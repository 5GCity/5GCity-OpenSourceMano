/*
 * 
 *   Copyright 2016 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-vnfr-annotation
{
  namespace "http://riftio.com/ns/riftware-1.0/rw-vnfr-annotation";
  prefix "rw-vnfr-ann";

  import tailf-common {
    prefix tailf;
  }

  import rw-vnfr {
    prefix rw-vnfr;
  }

  import vnfr {
    prefix vnfr;
  }

  tailf:annotate "/vnfr:vnfr-catalog/rw-vnfr:vnfd-ref-count" {
    tailf:callpoint rw_callpoint;
  }

  tailf:annotate "/vnfr:vnfr-catalog/vnfr:vnfr/rw-vnfr:operational-events" {
    tailf:callpoint rw_callpoint;
  }

  tailf:annotate "/rw-vnfr:vnfr-console" {
    tailf:callpoint rw_callpoint;
  }

}
