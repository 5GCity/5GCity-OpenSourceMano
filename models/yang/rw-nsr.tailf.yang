/*
 * 
 *   Copyright 2016 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-nsr-annotation
{
  namespace "http://riftio.com/ns/riftware-1.0/rw-nsr-annotation";
  prefix "rw-nsr-ann";

  import tailf-common {
    prefix tailf;
  }

  import rw-nsr {
    prefix rw-nsr;
  }

  import nsr {
    prefix nsr;
  }

  tailf:annotate "/nsr:ns-instance-opdata/nsr:nsr/rw-nsr:operational-events" {
    tailf:callpoint rw_callpoint;
  }

  tailf:annotate "/nsr:ns-instance-opdata/rw-nsr:nsd-ref-count" {
    tailf:callpoint rw_callpoint;
  }
}
